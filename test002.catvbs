Language="VBSCRIPT"


Dim oDoc As Document
Dim oPart As Part
Dim oBodies As Bodies
Set oDoc = CATIADocuments.Add( "Part")
Set oPart = oDoc.Part
Set oBodies = oPart. Bodies


Const Pi = 3. 14159265358979
Public dCamSetDis As Double
Public dBearingRadius As Double
Public dCamThickness As Double
Public dDriveWheelRadius As Double
Dim oRefPlane As Reference

dCamSetDis = 1
dBearingRadius = 2
dCamThickness = 3
dDriveWheelRadius = 4

Sub CreateCamCdAngle As Double, dRefDis As Double)
    Dim oSketch As Sketch
    Set oSketch= oBody. Sketches. Add(oRefPlane)
    Dim oFactory2D As Factory2D
    Set oFactory2D= oSketch. OpenEdition
    Dim oLineH As Line2D, oPtO As Point2D
    Set oLineH = oSketch. AbsoluteAxis. HorizontalReference
    Set oPtO = oSketch. AbsoluteAxis. Origin
    Dim oLineConst As Line2D
    Set oLineConst = oFactory2D. CreateLine(O, 0 , 50 ，的
    oLineConst. StartPoint = oPtO
    oLin正onst. Construction = True
end Sub
